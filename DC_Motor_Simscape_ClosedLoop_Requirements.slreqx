# DC_Motor_Simscape_ClosedLoop_Requirements

## REQ_DCM_001: When the speed command step occurs at 0.05 s, the DC motor speed controller shall command TargetSpeedRPM (600 rpm). (Functional)
Draft requirement derived from the target speed source and tuned model behavior. The model currently applies a 600 rpm target at 0.05 s.
- Rationale: Defines the commanded operating point used for closed-loop speed-control evaluation.
- Keywords: draft, auto-generated, command, speed

## REQ_DCM_002: While a target speed is commanded, the DC motor speed controller shall regulate measured speed to the commanded speed using proportional gain Kp (0.4) and integral gain Ki (1200). (Functional)
Draft requirement derived from closed-loop speed error and PI control behavior.
- Rationale: Provides closed-loop speed tracking and removes steady-state speed error.
- Keywords: draft, auto-generated, control, speed

## REQ_DCM_003: If the voltage command exceeds VoltageCommandMax (12 V) or falls below VoltageCommandMin (0 V), then the DC motor speed controller shall clamp the voltage command to the valid range. (Functional)
Draft requirement derived from the PI output limits and downstream voltage limiting behavior.
- Rationale: Prevents invalid motor-drive commands and matches the 12 V actuator limit.
- Keywords: draft, auto-generated, saturation, safety, voltage

## REQ_DCM_004: If the voltage command is saturated, then the DC motor speed controller shall use clamping anti-windup to limit integrator windup. (Functional)
Draft requirement derived from the PID Controller output-limit and AntiWindupMode settings.
- Rationale: Improves recovery from actuator saturation and keeps the controller state bounded.
- Keywords: draft, auto-generated, anti-windup, control, saturation

## REQ_DCM_005: The DC motor plant shall represent a permanent-magnet motor with RatedVoltage (12 V), RatedSpeed (1000 rpm), MaxSpeed (1200 rpm), BackEMFConstant (0.012 V/rpm), RotorInertia (100 g*cm^2), and ViscousDamping (1e-5 N*m*s/rad). (Functional)
Draft requirement derived from the PM DC Motor block parameterization.
- Rationale: Captures the assumed physical plant used to evaluate controller behavior.
- Keywords: draft, auto-generated, plant, motor, simscape

## REQ_DCM_006: The DC motor measurement interface shall report measured speed in rpm, measured current in A, voltage command in V, and target speed in rpm. (Functional)
Draft requirement derived from sensor conversion, unit conversion, and top-level output ports.
- Rationale: Provides observable signals required for tuning, verification, and diagnostics.
- Keywords: draft, auto-generated, interface, measurement, logging

## REQ_DCM_007: The DC motor model shall convert measured angular speed from SpeedUnitIn (rad/s) to SpeedUnitOut (rpm) using RadPerSecToRPMGain (60/(2*pi)). (Functional)
Draft requirement derived from the speed converter and gain used before feedback and output logging.
- Rationale: Ensures the feedback signal and reported speed use the same unit as the speed command.
- Keywords: draft, auto-generated, conversion, speed, units

## REQ_DCM_008: When simulation is run, the DC motor model shall save speed, current, voltage command, and target speed outputs to MotorOutputsDataset (motorOutputs). (Functional)
Draft requirement derived from top-level output logging and model output-save configuration.
- Rationale: Preserves simulation evidence needed for response-time and overshoot review.
- Keywords: draft, auto-generated, logging, simulation, dataset

## REQ_DCM_009: When a StepSetpoint (600 rpm) is applied at StepTime (0.05 s), the DC motor speed output shall have overshoot less than OvershootLimit (5%) and settle within SettlingTimeLimit (10 ms) of the step input. (Functional)
Draft performance requirement derived from the requested 600 rpm step-response acceptance criteria. The speed output is assessed against the 600 rpm target using the measured speed_rpm signal. The settling-time limit has been updated from 1 ms to 10 ms for the current acceptance target.
- Rationale: Defines the dynamic response acceptance criteria for the speed-control model and provides a repeatable threshold for tuning iterations.
- Keywords: draft, auto-generated, performance, step-response, speed, acceptance-criteria
